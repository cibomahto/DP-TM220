#usage "Generate a CSV file suitable for TM240A Pick n Place\n"
"Created by Dangerous Prototypes.com\n"
"Ian Lesnet (Feb. 18, 2013)\n"
"Parts of the code from Xinort\n"
"Modified with GUI enhancement by Jamz\n"
"1.0e\n"
// -----------------------


//------------------------------------Variables ---------------------------------------------------//
int debug=0;    				 // set to one for debug: show variables
int run_version=1;               // which implementation to run? valid values 0 and 1     
string VERSION = "1.0g";
//int MAXREEL=16;                  // 16 Reels for tm220a
int MAXREEL=24;                  // 24 Reels for TM240A
int YES= 1;
int NO = 0;
int found;
int counter=0;  				// use to know how many parts (elements) are there in the board, including Logo,name etc
int Result=0;
string SourceFname="";         	// file name of current board 
string StackFname;            	// Stack configuration filename
string workdir;               	// file save directory
string csvnametop="";        	// CSV file Top
string csvnamebottom="";     	// CSV file Bottom
real Xorigin=0.00;
real Yorigin=0.00;
int line = 1;

int Selected = 0; 

int i,j,k,l,m,n=0; 				//general purpose iteration/index variable 
// --------------------------------------------Display clickable Picture, linked to DP ------------------------------------------ 
string Text ="<br><br><center><a href='http://dangerousprototypes.com/2013/02/21/workshop-video-56-tm220a-table-top-pick-and-place-overview/'>"
				          "<img src=http://dangerousprototypes.com/wp-content/media/2013/02/15Reels.jpg align='Center' /></a></center><br><br>";

string Help1="<p><strong>Reel Name</strong> - Enter the Your Assigned name to the Reel</p>"
"<p><strong>Height</strong> - Enter the Height for the Reel. Valid values are 0.00 to 3.00.</p>"
"<p><strong>Rate</strong> - Enter Feeding Rate. Valid values are 0 to 20.</p>"	
"<p><strong>Rotation Correction</strong> - If Parts' placement rotation is off, select rotation value to add. a <strong>180</strong> degree rotation rotates the reel's part by 180.</p>";					  
string Help2="<br/><p><strong>Load Dangerous Prototype's Standard Stack</strong> - This button loads the Dangerous Prototypes' Standard Stack. </p>"
"<p><strong>Accept</strong> - Accept the dsplayed values. "
"If there are reel assignments under the tabs<strong> PCB Top</strong> and<strong> PCB Bottom</strong>, it will be updated, as well as the values  in <strong>Height</strong> and <strong>Rate</strong>.</p>";

						  
						  // DP's Common Parts offset use '|' as separator 
					  //Package|x|y|Comment	  
string DP_Packages[]={"0402|0.00|0.05|0402",
					  "0603|-0.40|-0.10|0603",
					  "0805|0.05|0.00|0805",
					  "1206|0.23|0.00|1206",
					  "EOL|0.00|0.00|EOL"};       // EOL - End of line indicator
                      // Reel#|Size|Part|Package|height|rate|RotationCorrection:0=0,1=90,2=180,3=270
string DPpartlist[] = {"0|Tray|Free|IC and Chips|0|1|0",
					   "1|8mm|Free|-|0|1",
					   "2|8mm|BAS-16J diode|DO-323|.5|1",
					   "3|8mm|1.5Amp ferrite bead|0603|.5|1",
					   "4|8mm|3.3volt regulator|SOT-23-5|.5|1", 
					   "5|8mm|LED Yellow|0805 (0603)|.5|1", 
					   "6|8mm|18pF capacitor|0603|.5|1",
					   "7|8mm|0.1uF capacitor|0603|.5|1",
					   "8|8mm|1uF capacitor|0603|.5|1",
					   "9|8mm|10uF capacitor|CASE A (1206)|.5|1", 
					   "10|8mm|2K resistor|0603|.5|1", 
					   "11|8mm|10K resistor|0603|.5|1", 
					   "12|8mm|10K x 4 resistor array|1206|.5|1", 
					   "13|12mm|SMD button|5.4mm|.5|1",
					   "14|12mm|Free|-|0|1",
					   "15|16mm|Free|-|0|1" };

int  DP_stack_Loaded =0;     // flag 1 if dp stack is loaded


// array for each individual parts as found in the pcb
//struct {
	string Ename[];             // Parts name
	string Evalue[];            // Parts value
	string Epackagename[];       // Package 
	string ElibrarySource[];    // Library source
	string EpartsX[];           // x coordinate
	string EpartsY[];           // y coordinate
	string Elayer[];            // layer - Top/Bottom 
	string Eangle[];               // angle of placement
	int Efeeder[];
	real Eheight[];
	int  Eptr[];                 //Line number, fills in number to track line an index ptr
// }


// Array to Hold for display by grouping 
// struct {
    int g_class[];                // Used to group parts use variable grouping
	int g_ptr[];                 // pointer to array # of this structure
	string g_Ename[];            //Parts name e.g. c1,c2,c3
	string g_Evalue[];           // parts value e.g 1uf
	string g_Epackagename[];     // Package name like C0603
	string g_ElibrarySource[];    // library 
	string g_EpartsX[];          // x coordinate of parts
	string g_EpartsY[];          // y coordinate of parts 
	string g_Elayer[];           // PCB layer - Top, Bottom
	int g_Head[];                // Head - 1 or 2  used by tm220a
	real g_Eheight[];            // height of parts used bu tm220, set to 0 as default
	int g_Equantity[];           // count of parts with same value
	int g_Erate[];               // feeder Rate  used by tm220a ( 0,1,2 .. 20?)
	string g_Eangle[];              // Angle of rotation of pats
	int g_TapeSkip[];            // Tape skip  used by tm220a
	int g_Efeeder[];             // hold feeder assignment, initially 99 for no assignment
	string g_backptr[];
// }
int grouping=0;
int ReelNo_Top[]; 
int ReelNo_Bottom[];                      // Reel # 0 to 15 
int index=0;				      // counter for array the holds the group partlist
//struct {  // used after separting the top and bottom layer
int CT_ReelNo[];  // holds the reelno 0-15,99
string CT_EpartsX[];
string CT_EpartsY[];
string CT_Epackagename[];
string CT_Evalue[];				
string CT_Elayer[];
real CT_Eheight[];
int CT_Ehead[];
int CT_Skip[];
int CT_Rate[];
int CT_class[];
string CT_backptr[];   
// }
// struct {
int CB_ReelNo[];  // holds the reelno 0-15
string CB_EpartsX[];
string CB_EpartsY[];
string CB_Epackagename[];
string CB_Evalue[];				
string CB_Elayer[];
real CB_Eheight[];
int CB_Ehead[];
int CB_Skip[];
int CB_Rate[];
int CB_class[]; 
string CB_backptr[];  
// }

//struct {  // Top - variables f
int g_Efeeder_Top[];
int g_Head_Top[];          		
real g_Eheight_Top[];	 
int g_TapeSkip_Top[];	
int g_Erate_Top[]; 
// }
//struct {   // bottom
int g_Efeeder_Bottom[];
int g_Head_Bottom[];          		
real g_Eheight_Bottom[];	 
int g_TapeSkip_Bottom[];	
int g_Erate_Bottom[]; 
// }


real BoardX =0.00;   			  // size of pcb board in x axis  (lower left)
real BoardY =0.00;    			 // size of pcb board in y axis  (lower left) 
int nBoardsinX=0;  				 // no. of boards in x direction
int nBoardsinY=0; 				 // no. of Boards in Y direction
real GapBoardX =0.00; 			 // gap between boards
real GapBoardY =0.00;  			 // gap between boards

string components_Top[];     	 //  concatenation of variables for top layer: g_name+value+package use in combobox
string component_quantity_Top[]; // version 1 update - break components_Top
string component_value_Top[];
string component_packagename_Top[];

string components_Bottom[];   	 //  concatenation of variables for bottom: g_name+value+package use in combobox
string component_quantity_Bottom[];
string component_value_Bottom[];
string component_packagename_Bottom[];
int comboSelected_Top[];         	 //  ptr to array of grouped components for above used as combobox selector
int comboSelected_Bottom[];         	 //  ptr to array of grouped components for above used as combobox selector

int components_Bottom_ptr[]; 	 //  will hold the pointer to the array for  components_Bottom[];
int components_Top_ptr[];        //  will hold the pointer to the array for  components_Top[];
int TopCounter=0,BottomCounter=0; // Top components counter and Bottom component Counter
int len;

string partslist[];
string partsX; 
string partsY; 
string partsRotation;
string layer;
string Reel[];
string ReelAlias[];     // user defined names for reels
real ReelHeight[];
int ReelRate[];
string RotationOffset[];    // 0,90,180,270 - adds angle
int RotationOffsetSelected[];   // 0-3    , 
int xmax =-2147483648;             
int xmin = 2147483647;
int maxComboLen_Top = -1;   // maximum lenght of string in the combobox
int maxComboLen_Bottom = -1;   // maximum lenght of string in the combobox

//-------------------------------------------------------------------------------------------------------
//  convert num to string
string Num2Str(int i)   { 
	string str;
	sprintf(str, "%d", i);
 return str; }

//trim leading and trailing spaces

string alltrim(string s)
{
  while (s && isspace(s[0])) {
		s = strsub(s, 1);
	}
  while (s && isspace(s[strlen(s) - 1])) {
		s = strsub(s, 0, strlen(s) - 1);
	}
  if (strlen(s)==0) s=" ";	
  
  return s;
}
string pad_all(string text,int size,string chr) {
	int len=strlen(text);
	int lr=(size-len)/2;
	int z;
	string ret;
	string xl;
	for (z=0;z <lr;z++) {
	  xl+=chr;
	}
	ret=xl+text+xl;
    return ret;
}

void Load_Stack(void) {
    string a[];    // use for spliting the line
	int i;
	for (i=0; i < MAXREEL;i++) {
	//	Reel[i+1]="Reel# "+Num2Str(i);     // remember to subtract 1, Reel[0]="--------";
	//	ReelAlias[i+1]=Reel[i+1];
		n = strsplit(a,DPpartlist[i], '|'); 
		if( strtol(alltrim(a[0]))==i ) {
		   ReelAlias[i+1]= alltrim(a[2])+" ("+alltrim(a[3])+")";
		   ReelHeight[i+1]= strtod(alltrim(a[4]));
		   ReelRate[i+1]=strtol(alltrim(a[5]));
		}
	}

}

// Initialize variables
Reel[0]="--------";
ReelAlias[0]=Reel[0];

for (i=0; i < MAXREEL ;i++) {
  g_Efeeder_Top[i]=99;
  g_Efeeder_Bottom[i]=99;
  comboSelected_Top[i]=0;
  comboSelected_Bottom[i]=0;
  RotationOffsetSelected[i]=0;
  if (run_version==0) {
	  ReelNo_Top[i]= 99;
	  ReelNo_Bottom[i]= 99;
  } 
  if (run_version==1) {
	Reel[i+1]="Reel# "+Num2Str(i); 
	ReelAlias[i+1]=Reel[i+1];
  }	
  g_Head_Top[i]=1; 
  g_Head_Bottom[i]=1;   
  g_Eheight_Top[i]=0.00;
  g_Eheight_Bottom[i]=0.00;  
  g_TapeSkip_Top[i]=0;	
  g_TapeSkip_Bottom[i]=0;	
  g_Erate_Top[i]=0; 
  g_Erate_Bottom[i]=0; 
 
  
  
  
}
for (i=0; i< 4;i++) {
    RotationOffset[i]=Num2Str(i*90);
}

if (project.board) project.board(B) {
	workdir=filedir(B.name);
	SourceFname=filename(B.name);
	// remove extension
	string s = SourceFname;
	char c = '.';
	int pos = strrchr(s, c);
	if (pos >= 0) {
		s[pos]='\0';
		SourceFname=s;
	} 
    StackFname=workdir+SourceFname+".PnP";   // same filename with the board

	//---- try to get all parts in the board loaded to memory
	//     Ename[j],Equantity[j],Evalue[j],Epackagename[j] etc
		
		
	B.elements(E) {
	  
      if (E.mirror == 0)
        layer = "Top";
      else
        layer = "Bottom";

      sprintf(partsX, "%.2f", u2mm(E.x));
      sprintf(partsY, "%.2f", u2mm(E.y));
	  sprintf(partsRotation,"%.2f",E.angle);
	  Ename[counter]=E.name;
	  Evalue[counter]=E.value;
	  Epackagename[counter]=E.package.name;
	  ElibrarySource[counter]=E.package.library;
	  EpartsX[counter]=partsX;
	  EpartsY[counter]=partsY;
	  Elayer[counter]=layer;	
	  Eangle[counter]=partsRotation; 
      Eptr[counter]=counter;   //  line numbers, when Eptr[0] ,value is 0  
	  counter++;							
	}
	
	

	  // then group contents according to values and package, must create a group 
	   // index holds all the unique elements after grouping.
	found=0;
	
	for (j=0;j<counter;j++) {
	    if (index==0) {     // initial content 
			g_Ename[index]=alltrim(Ename[j]);
			g_Evalue[index]=alltrim(Evalue[j]);
			g_Epackagename[index]=alltrim(Epackagename[j]);
	        g_ElibrarySource[index]=ElibrarySource[j];
			g_EpartsX[index]="";     // EpartsX[j];     //coordinates parts-do not use
			g_EpartsY[index]="";     // EpartsY[j];
			g_Elayer[index]=Elayer[j];
			g_Efeeder[index]= 99;   // to be filled up- reel assignment
			g_Head[index]=1;     // valid values are 1 and 2 only
 			g_Equantity[index]=1;   // always 1
			g_Erate[index]=0;      // to be filled up
			g_Eangle[index]="";     
			g_Eheight[index]=0.0;     // to be filled up
			g_ptr[index]=index;        // each line must have a number
            g_class[index]=grouping;			
			g_backptr[index]= alltrim(Num2Str(Eptr[j]));
            index++;			
		} else {
		    // locate the part and group(package, value, layer)
			found=0;   // not found yet
			for(i=0;i < index;i++) {
			    if ( strupr(alltrim(Epackagename[j])) == strupr(g_Epackagename[i]) ) {			
				    if ( strupr(alltrim(Evalue[j]))==strupr(g_Evalue[i]) )  {				
						if (Elayer[j] == g_Elayer[i]) {     // group
							g_Equantity[i]++;
							g_Ename[i]+=","+alltrim(Ename[j]);   // append so that parts name will be c1,c2,c3 etc
							g_class[i]=grouping;
							g_backptr[i]+="|"+alltrim(Num2Str(Eptr[j]));           // points back 5|12|13|16|22
							found=1; // found one
						}	 
					}
				}
			}
		    if (found==0) {   // found nothing, create new entry, index was incremented before			  
				g_Ename[index]=alltrim(Ename[j]);
				g_Evalue[index]=alltrim(Evalue[j]);
				g_Epackagename[index]=alltrim(Epackagename[j]);
				g_ElibrarySource[index]=ElibrarySource[j];
				g_EpartsX[index]="";      //EpartsX[j];     //coordinates parts-Do not use
				g_EpartsY[index]="";      //EpartsY[j];
				g_Elayer[index]=Elayer[j];
				g_Efeeder[index]=99;   // to be filled up- reel assignment
				g_Head[index]=1;       // initially assigne head # 1
				g_Equantity[index]=1;   // always 1
				g_Erate[index]=0;      // to be filled up
				g_Eangle[index]="";     
				g_Eheight[index]=0.0;     // to be filled up
                g_ptr[index]=index; 
				g_class[index]=grouping;
				g_backptr[i]=alltrim(Num2Str(Eptr[j]));   
	            grouping++;				
				index++;
			}
		    
		}
	
	   
	}
	    		
		
		//   Contents are kept here:
		
	
	// find the largest string in the array for alignement of display
	int teststring;	
	if (run_version==0) {
		components_Top[TopCounter++]   ="*****Not Used*****";   	
		components_Bottom[BottomCounter++]="*****Not Used*****";  
	}
	
	for (j=0;j< index;j++) {	   //load for display		    
		string equant=Num2Str(g_Equantity[j]); 			 
		string gptr=Num2Str(g_ptr[j]);			
		partslist[j] = g_Ename[j] + " \t" +equant+" \t"+ g_Evalue[j] + " \t" + g_Epackagename[j] + " \t" + g_ElibrarySource[j] + " \t"+g_Elayer[j];
				
		if (g_Elayer[j]=="Top")	{	
			components_Top_ptr[TopCounter]=j;   // keep track of component
			string gxname;
			if (run_version==0) {
				sprintf(gxname,"%-s\t%-s\t%-s\t%-s",alltrim(g_Ename[j]),alltrim(equant),alltrim(g_Evalue[j]),alltrim(g_Epackagename[j]));      
				components_Top[TopCounter]=gxname;	
			}
			if (run_version==1) {
				components_Top[TopCounter]=alltrim(g_Ename[j]);
				component_quantity_Top[TopCounter]=alltrim(equant);
				component_value_Top[TopCounter]=alltrim(g_Evalue[j]);
				component_packagename_Top[TopCounter]=alltrim(g_Epackagename[j]);
				CT_Eheight[TopCounter]=0.00;
				CT_Ehead[TopCounter]=1;
				CT_Skip[TopCounter]=0;
				CT_Rate[TopCounter]=0;
	        }
			    
		//	components_Top[TopCounter]=g_Ename[j] + " \t" +equant+" \t"+ g_Evalue[j] + " \t" + g_Epackagename[j] ;		
			int combolen_Top=strlen(components_Top[TopCounter]);			
			if ( combolen_Top> maxComboLen_Top) {
			       maxComboLen_Top=combolen_Top;
			}
			if (run_version==0) {
				CT_ReelNo[TopCounter]=99;  // holds the reelno 0-15
			}
			if (run_version==1) {
				CT_ReelNo[TopCounter]=0;  // used as selections, will contains reel # selected
			}
			CT_EpartsX[TopCounter]=g_EpartsX[j];
			CT_EpartsY[TopCounter]=g_EpartsX[j];			
			CT_Epackagename[TopCounter]=g_Epackagename[j];				
			CT_Evalue[TopCounter]=g_Evalue[j];				
			CT_Elayer[TopCounter]=g_Elayer[j];
			CT_class[TopCounter]= g_class[j]; 
            CT_backptr[TopCounter]=g_backptr[j];		
			TopCounter++;
			
        } else {
			components_Bottom_ptr[BottomCounter]=j;
			string gxname;
			if (run_version==0) {
			sprintf(gxname,"%-s\t%-s\t%-s\t%-s",alltrim(g_Ename[j]),alltrim(equant),alltrim(g_Evalue[j]),alltrim(g_Epackagename[j]));
		  //  components_Bottom[BottomCounter]=g_Ename[j] + " \t" +equant+" \t"+ g_Evalue[j] + " \t" + g_Epackagename[j] ;	
		    components_Bottom[BottomCounter]=gxname;
			}
			if (run_version==1) {
				components_Bottom[BottomCounter]=alltrim(g_Ename[j]);
				component_quantity_Bottom[BottomCounter]=alltrim(equant);
				component_value_Bottom[BottomCounter]=alltrim(g_Evalue[j]);
				component_packagename_Bottom[BottomCounter]=alltrim(g_Epackagename[j]);
				CB_Eheight[BottomCounter]=0.00;
				CB_Ehead[BottomCounter]=1;
				CB_Skip[BottomCounter]=0;
				CB_Rate[BottomCounter]=0;
	        }	
		    int combolen_Bottom=strlen(components_Bottom[BottomCounter]);			
			if ( combolen_Bottom> maxComboLen_Bottom) {
			       maxComboLen_Bottom=combolen_Bottom;
			}
			if (run_version==0) {
				CB_ReelNo[BottomCounter]=99;  // holds the reelno 0-15
			}	
			if (run_version==1) {
				CB_ReelNo[BottomCounter]=0;  // initially select reel 0
			}
			CB_EpartsX[BottomCounter]=g_EpartsX[j];
			CB_EpartsY[BottomCounter]=g_EpartsX[j];
			CB_Epackagename[BottomCounter]=g_Epackagename[j];
			CB_Evalue[BottomCounter]=g_Evalue[j];				
			CB_Elayer[BottomCounter]=g_Elayer[j];
			CB_class[BottomCounter]= g_class[j];    //grouping
			CB_backptr[BottomCounter]=g_backptr[j];	
			BottomCounter++;
		}
		
	}
	if (run_version==0) {
		maxComboLen_Top=maxComboLen_Top+5;  // add 10 spaces		
		maxComboLen_Bottom=maxComboLen_Bottom+5;  // add 10 spaces	
		string not_used=pad_all("Not Used",maxComboLen_Top,"*");
		components_Top[0]=not_used;	
		components_Bottom[0]=not_used;
	}
	// load values from stack file
	
	if (filesize(StackFname)> 0) {
	    string lines[];
		int tc=0;
		int tb=0;
		int tr=0;
	    int nLines = fileread(lines, StackFname);  // returns # of lines read
		
			for(i=0;i < nLines;i++) {  
				string a[];    // use for spliting the line
				n = strsplit(a,lines[i], '|'); 
				if( alltrim(a[0])=="[TOP]" ) {
					if (run_version==0) {
						comboSelected_Top[tc]=strtol(alltrim(a[1]));	
						g_Head_Top[tc]=strtol(alltrim(a[2]));          		
						g_Eheight_Top[tc]=strtod(alltrim(a[3]));	 
						g_TapeSkip_Top[tc]=strtol(alltrim(a[4]));	
						g_Erate_Top[tc]=strtol(alltrim(a[5])); 
						
						if (comboSelected_Top[tc]==0) {
						   ReelNo_Top[tc]=99;
						} else {
						   ReelNo_Top[tc]= comboSelected_Top[i];
						}
						
					}
					if (run_version==1) {
						if ( components_Top[tc]==alltrim(a[1])) {				
							CT_ReelNo[tc]=strtol(alltrim(a[2]));
							CT_Ehead[tc]=strtol(alltrim(a[3]));
							CT_Eheight[tc]=strtod(alltrim(a[4]));	
							CT_Skip[tc]=strtol(alltrim(a[5])); 
							CT_Rate[tc]=strtol(alltrim(a[6])); 
						}
					}
					tc++;
				}
				if(alltrim(a[0])=="[BOTTOM]") {		
					if (run_version==0) {
						comboSelected_Bottom[tb]=strtol(alltrim(a[1]));	
					//	dlgMessageBox("!Start comboSelected_Bottom["+Num2Str(i)+"]= "+Num2Str(comboSelected_Bottom[i])+"\n"+"comboSelected_Bottom[0] ="+Num2Str(comboSelected_Bottom[0])+"\n","&OK"); 
						g_Head_Bottom[tb]=strtol(alltrim(a[2]));          		
						g_Eheight_Bottom[tb]=strtod(alltrim(a[3]));	 
						g_TapeSkip_Bottom[tb]=strtol(alltrim(a[4]));	
						g_Erate_Bottom[tb]=strtol(alltrim(a[5])); 
						
						if (comboSelected_Bottom[tb]==0) {
						   ReelNo_Bottom[tb]=99;
						} else {
						   ReelNo_Bottom[tb]= comboSelected_Bottom[tb];
						}
						
					//	dlgMessageBox("! End comboSelected_Bottom["+Num2Str(i)+"]= "+Num2Str(comboSelected_Bottom[i])+"\n","&OK"); 
					}
					if (run_version==1) {
						if (components_Bottom[tb]==alltrim(a[1])) {
							CB_ReelNo[tb]=strtol(alltrim(a[2]));
							CB_Ehead[tb]=strtol(alltrim(a[3]));
							CB_Eheight[tb]=strtod(alltrim(a[4]));	
							CB_Skip[tb]=strtol(alltrim(a[5])); 
							CB_Rate[tb]=strtol(alltrim(a[6])); 
						}	
					}
					tb++;
				}
				if(alltrim(a[0])=="[REEL]") {
					if (run_version==1) {
						if(tr==strtol(alltrim(a[1]))) {
							ReelAlias[tr+1]=alltrim(a[2]);
							ReelHeight[tr+1]=strtod(alltrim(a[3]));
							ReelRate[tr+1]=strtol(alltrim(a[4]));
							RotationOffsetSelected[tr+1]=strtol(alltrim(a[5])); 
							
						  
						}
					}	
					tr++;
				}	
				// Load ReelAlias Reel[]
				for (j=0; j < MAXREEL;j++) {
					Reel[j+1]=ReelAlias[j+1];
				
				}
				
	
			
			}
				//dlgMessageBox("!Final: comboSelected_Bottom[0]= "+Num2Str(comboSelected_Bottom[0])+"\n","&OK"); 
	
	}
	Result=5;
while (Result == 5)
	Result = dlgDialog("DP TM240A Pick and Place ") {
		dlgTabWidget {
			dlgTabPage("CSV Export") {
				
				dlgHBoxLayout {
					dlgStretch(1);
					dlgLabel("Dangerous Prototypes TM240A Pick n Place\n                     Version "+VERSION);
					dlgStretch(1);
				}
				
				dlgHBoxLayout {			   
				
		        
			     dlgTextView(Text); 		 
		
				
					
				}
				
				// dlgHBoxLayout {
				// dlgLabel("Home: X and Y origin:           ");
				// dlgRealEdit(Xorigin, 0.00, 280.00);
				// dlgRealEdit(Yorigin, 0.00, 280.00);
				// dlgSpacing(700);
				// dlgStretch(1);	
					
				// }
				// dlgHBoxLayout {
					// dlgLabel("Size of PCB Board:              ");
					// dlgRealEdit(BoardX, 20.00, 220.00);
					// dlgRealEdit(BoardY, 20.00, 200.00);
					// dlgSpacing(700);
					// dlgStretch(1);
					
				// }
				// dlgHBoxLayout {
					// dlgLabel("Number of Boards in X direction:");
					// dlgIntEdit(nBoardsinX,0,20);
						// dlgSpacing(700);
					// dlgStretch(1);
					
				// }
				// dlgHBoxLayout {
					// dlgLabel("Number of Boards in Y direction:");
					// dlgIntEdit(nBoardsinY,0,20);
						// dlgSpacing(700);
					// dlgStretch(1);
					
				// }
				// dlgHBoxLayout {
					// dlgLabel("Gap in mm between Boards in X direction:");
					// dlgRealEdit(GapBoardX, -100.00, 300.00);
						// dlgSpacing(700);
					// dlgStretch(1);
					
				// }
				// dlgHBoxLayout {
					// dlgLabel("Gap in mm between Boards in Y direction:");
					// dlgRealEdit(GapBoardY, -100.00, 300.00);
						// dlgSpacing(700);
					// dlgStretch(1);
					
				// }
				dlgHBoxLayout {
					dlgLabel("Enter CSV Export File (TOP):");					
					csvnametop=workdir+SourceFname+"_Top.csv";				
					dlgStringEdit(csvnametop);					
					dlgPushButton("Browse") {					 
						csvnametop= dlgFileSave("Save Exported CSV", filesetext(B.name, ".csv"), "*.csv");
					}
				}
				dlgHBoxLayout {
					dlgLabel("Enter CSV Export File (Bottom):");					
					csvnamebottom=workdir+SourceFname+"_Bottom.csv";				
					dlgStringEdit(csvnamebottom);					
					dlgPushButton("Browse") {					 
						csvnamebottom= dlgFileSave("Save Exported CSV", filesetext(B.name, ".csv"), "*.csv");
					}
				}
				dlgHBoxLayout {	
					dlgLabel("Enter output Directory:");
					// StackFname=workdir+SourceFname+".PnP";
					dlgStringEdit(StackFname);										
					dlgPushButton("browse") {						
						StackFname = dlgFileSave("Save TM240a Stack", filesetext(B.name, ".PnP"), "*.PnP");
					}
				}
				
				dlgSpacing(10);
				dlgHBoxLayout {
					dlgStretch(1);
					dlgPushButton("+OK")    dlgAccept();
					dlgPushButton("Cancel") dlgReject();
				}
				dlgHBoxLayout {
					dlgStretch(1);
					
				}
			}
			
			dlgTabPage("Part list") {
				dlgHBoxLayout {
					dlgStretch(1);
					dlgLabel("Parts in the Board");
					dlgStretch(1);
				}
				dlgHBoxLayout {		
					Selected= -1;
					dlgListView("Part\tQuantity\tValue\tPackage\tLibrary\tLayer", partslist,Selected);
				
				}
				
			
			}
			dlgTabPage("PCB Top") {
			    dlgRedisplay();
			    if (run_version==0) {
					dlgVBoxLayout {
						int celly=0;
						dlgGridLayout {
						dlgCell(0,celly++) {
		
						//	dlgMessageBox("!Value of maxComboLen_Top="+Num2Str(maxComboLen_Top*8), "&OK");   				
							string pl="<table width='100%'>"+
							"<tr><td width='60'>Reel #</td>"+
							"<td width='"+Num2Str(maxComboLen_Top*9)+"'>Parts Label/Quantity/Value/Package</td>"+
							"<td width='55'>Head</td>"+
							"<td width='70'>Height</td>"+
							"<td width='55'>Skip</td>"+
							"<td width='20'>Rate</td>"+
							"</tr>"+
							"</table>";
							dlgLabel(pl);
							dlgStretch(1);
							}
										
						}
						dlgGridLayout {
							int j=0;						
							for (j=0;j<MAXREEL;j++) {		
								int k=0;
								dlgCell(j, k) {										
									dlgLabel("Reel #"+Num2Str(j));
									dlgSpacing(5);							
									k++;							
								}
										
								dlgCell(j, k) {		
									switch (j) {
										case 0:  	dlgComboBox(components_Top, comboSelected_Top[0]) {
														
														// comboSelected_Top[0]: from 0 to max number of elements in components_Top
														  if(comboSelected_Top[0]==0) {  // ="*****Not used*****" 
															g_Efeeder_Top[comboSelected_Top[0]]=99;         // assign 99
														} else { 
															// components_Top[comboSelected_Top[0]]     selected content in string
															// components_Top_ptr[n]   // keep track of component
															// components_Top[n]=g_Ename[j] + "  " +equant+"  "+ g_Evalue[j] + "  " + g_Epackagename[j] ;		
															g_Efeeder_Top[comboSelected_Top[0]]=0; //selected content assign to feeder # 0
			
														}
														ReelNo_Top[0]= comboSelected_Top[0];	// Reel 0 is assigned with selected line
														CT_ReelNo[comboSelected_Top[0]]=0;  		
													}
													break;
										case 1:  	dlgComboBox(components_Top, comboSelected_Top[1]) {
														if(comboSelected_Top[1]==0) {
															g_Efeeder_Top[comboSelected_Top[1]]=99;
														} else { 		
															g_Efeeder_Top[comboSelected_Top[1]]=1;
															
														}
														ReelNo_Top[1]=comboSelected_Top[1];
														CT_ReelNo[comboSelected_Top[1]]=1; 
													}
													break;	
										case 2:  	dlgComboBox(components_Top, comboSelected_Top[2]) {
														if(comboSelected_Top[2]==0) {
															g_Efeeder_Top[comboSelected_Top[2]]=99;
														} else {
															g_Efeeder_Top[comboSelected_Top[2]]=2;
														}
														ReelNo_Top[2]=comboSelected_Top[2];	
														CT_ReelNo[comboSelected_Top[2]]=2; 
													}
													break;
										case 3:  	dlgComboBox(components_Top, comboSelected_Top[3]) {
														if(comboSelected_Top[3]==0) {
															g_Efeeder_Top[comboSelected_Top[3]]=99;
														} else {
															g_Efeeder_Top[comboSelected_Top[3]]=3; 	
														}
														ReelNo_Top[3]=comboSelected_Top[3];	
														CT_ReelNo[comboSelected_Top[3]]=3; 
													}
													break;
										case 4:  	dlgComboBox(components_Top, comboSelected_Top[4]) {
														if(comboSelected_Top[4]==0) {
															g_Efeeder_Top[comboSelected_Top[4]]=99;
														} else {
															g_Efeeder_Top[comboSelected_Top[4]]=4;
														}
														ReelNo_Top[4]=comboSelected_Top[4];
														CT_ReelNo[comboSelected_Top[4]]=4; 	
													}	
													break;	
										case 5:  	dlgComboBox(components_Top, comboSelected_Top[5]) {
														if(comboSelected_Top[5]==0) {
															g_Efeeder_Top[comboSelected_Top[5]]=99;
														} else {
															g_Efeeder_Top[comboSelected_Top[5]]=5;
														}
														ReelNo_Top[5]= comboSelected_Top[5];
														CT_ReelNo[comboSelected_Top[5]]=5; 
																
													}
													
													break;			
										case 6:  	dlgComboBox(components_Top, comboSelected_Top[6]) {
														if(comboSelected_Top[6]==0) {
															g_Efeeder_Top[comboSelected_Top[6]]=99;
														} else {
															g_Efeeder_Top[comboSelected_Top[6]]=6;	
														}
														ReelNo_Top[6]=comboSelected_Top[6];
														CT_ReelNo[comboSelected_Top[6]]=6; 													
													}
													break;
										case 7:  	dlgComboBox(components_Top, comboSelected_Top[7]) {
														if(comboSelected_Top[7]==0) {
															g_Efeeder_Top[comboSelected_Top[7]]=99;
														} else {
															g_Efeeder_Top[comboSelected_Top[7]]=7;
														}
														ReelNo_Top[7]=comboSelected_Top[7];
														CT_ReelNo[comboSelected_Top[5]]=5; 	
														
													}
													break;	
										case 8:  	dlgComboBox(components_Top, comboSelected_Top[8]) {
														if(comboSelected_Top[8]==0) {
															g_Efeeder_Top[comboSelected_Top[8]]=99;
														} else {
															g_Efeeder_Top[comboSelected_Top[8]]=8;	
														}
														ReelNo_Top[8]=comboSelected_Top[8];	
														CT_ReelNo[comboSelected_Top[8]]=8; 	
													}
													break;
										case 9:  	dlgComboBox(components_Top, comboSelected_Top[9]) {
														if(comboSelected_Top[9]==0) {
															g_Efeeder_Top[comboSelected_Top[9]]=99;
														} else {
															g_Efeeder_Top[comboSelected_Top[9]]=9;
														}
														ReelNo_Top[9]=comboSelected_Top[9];	
														CT_ReelNo[comboSelected_Top[9]]=9; 	
													}
													break;
										case 10:  	dlgComboBox(components_Top, comboSelected_Top[10]) {
														if(comboSelected_Top[10]==0) {
															g_Efeeder_Top[comboSelected_Top[10]]=99;
														} else {
															g_Efeeder_Top[comboSelected_Top[10]]=10;	
														}
														ReelNo_Top[10]=comboSelected_Top[10];
														CT_ReelNo[comboSelected_Top[10]]=10; 	
													}
													break;	
										case 11:  	dlgComboBox(components_Top, comboSelected_Top[11]) {
														if(comboSelected_Top[11]==0) {
															g_Efeeder_Top[comboSelected_Top[11]]=99;
														} else {
															g_Efeeder_Top[comboSelected_Top[11]]=11;
																	
														}
														ReelNo_Top[11]=comboSelected_Top[11];
														CT_ReelNo[comboSelected_Top[11]]=11; 	
													}
													break;
										case 12:  	dlgComboBox(components_Top, comboSelected_Top[12]) {
														if(comboSelected_Top[12]==0) {
															g_Efeeder_Top[comboSelected_Top[12]]=99;
														} else {
															g_Efeeder_Top[comboSelected_Top[12]]=12;
														}
														ReelNo_Top[12]=comboSelected_Top[12];
														CT_ReelNo[comboSelected_Top[12]]=12; 	
													}
													break;
										case 13:  	dlgComboBox(components_Top, comboSelected_Top[13]) {
														if(comboSelected_Top[13]==0) {
															g_Efeeder_Top[comboSelected_Top[13]]=99;
														} else {
															g_Efeeder_Top[comboSelected_Top[13]]=13;
														}
														ReelNo_Top[13]=comboSelected_Top[13];
														CT_ReelNo[comboSelected_Top[13]]=13; 	
													}
													break;
										case 14:  	dlgComboBox(components_Top, comboSelected_Top[14]) {
														if(comboSelected_Top[14]==0) {
															g_Efeeder_Top[comboSelected_Top[14]]=99;
														} else {
															g_Efeeder_Top[comboSelected_Top[14]]=14;	
														}
														ReelNo_Top[14]=comboSelected_Top[14];
														CT_ReelNo[comboSelected_Top[14]]=14; 													
													}
													break;	
										case 15:  	dlgComboBox(components_Top, comboSelected_Top[15]) {
														if(comboSelected_Top[15]==0) {
															g_Efeeder_Top[comboSelected_Top[15]]=99;
														} else {
															g_Efeeder_Top[comboSelected_Top[15]]=15; 	
														}
														ReelNo_Top[15]=comboSelected_Top[15];
														CT_ReelNo[comboSelected_Top[15]]=15; 	
																
													}
													
													break;												
									}
									dlgStretch(1);
									dlgSpacing(5);							
									k++;							
								}	
								dlgCell(j, k) {						  
									dlgSpinBox(g_Head_Top[j],0,2);
									dlgSpacing(5);							
									k++;	
									
								}
								dlgCell(j, k) {	
									dlgRealEdit(g_Eheight_Top[j], 0.00, 3.00);	    												
									k++;
									//dlgSpacing(5);
														
								}
								 dlgCell(j, k) {	
									dlgSpinBox(g_TapeSkip_Top[j], 0,1 );
									k++;							
									dlgSpacing(5);
								}	
								 dlgCell(j, k) {	
									dlgSpinBox(g_Erate_Top[j],0,20 );
									k++;							
									dlgSpacing(5);
								}		
								
								dlgCell(j, k) {				
									dlgSpacing(5);
									dlgLabel(" ");
									//dlgStretch(2);		
									k++;							
								}
							}
						}
						
					}
					dlgVBoxLayout {
						dlgStretch(1);
					}
				}
                if (run_version==1) {
					dlgVBoxLayout {
						dlgGridLayout {
							int celly=0;
							dlgCell(0, celly++) {
								dlgVBoxLayout {
									dlgLabel("Parts Label            ");
									dlgSpacing(5);
									for (i=0; i < TopCounter;i++) {
										dlgLabel(components_Top[i]);
										dlgSpacing(6);
									}
									dlgStretch(1);
								}
								
							}
							 dlgCell(0, celly++) {
								dlgVBoxLayout {
									dlgLabel("Quantity ");
									dlgSpacing(5);
									for (i=0; i < TopCounter;i++) {
										dlgLabel(component_quantity_Top[i]);
										dlgSpacing(6);
									}
									
									dlgStretch(1);
								}
							 }	
							
							dlgCell(0, celly++) {
								dlgVBoxLayout {
									dlgLabel("Value    ");
									dlgSpacing(5);
									for (i=0; i < TopCounter;i++) {
										dlgLabel(component_value_Top[i]);
										dlgSpacing(6);
									}
									
									dlgStretch(1);
								}	
							}
							
							
							dlgCell(0, celly++) {
								dlgVBoxLayout {
									dlgLabel("Package");
									dlgSpacing(5);
									for (i=0; i < TopCounter;i++) {
										dlgLabel(component_packagename_Top[i]);
										dlgSpacing(6);
									}
									//dlgSpacing(5);
									dlgStretch(1);
								}	
							}
															
							 dlgCell(0,celly++) {
								dlgVBoxLayout {
									dlgLabel("Reel Assignment");
									for (i=0; i < TopCounter;i++) {	
										dlgComboBox(Reel, CT_ReelNo[i]) { 
											// if (DP_stack_Loaded==2) {
											      // CT_Rate[i]=ReelHeight[CT_ReelNo[i]];
												  // CT_Eheight[i]=ReelRate[CT_ReelNo[i]];
												  // dlgRedisplay();
												  	
											// }										
										} 									
									}
									dlgSpacing(5);
									dlgStretch(1);
								}	 
							 }
							 dlgCell(0, celly++) {
								dlgVBoxLayout {
									dlgLabel("Head");
									for (i=0; i < TopCounter;i++) {	
										dlgSpinBox(CT_Ehead[i], 1, 2);												
									}
									dlgSpacing(5);
									dlgStretch(1);
								}	
								
							}	
							dlgCell(0, celly++) {
								dlgVBoxLayout {
									dlgLabel("Height");
									for (i=0; i < TopCounter;i++) {	
										dlgRealEdit(CT_Eheight[i], 0.00, 3.00);												
									}
									dlgSpacing(5);
									dlgStretch(1);
								}	
							}	
							
							dlgCell(0, celly++) {
								dlgVBoxLayout {							
									dlgLabel("Skip");
									for (i=0; i < TopCounter;i++) {	
										dlgSpinBox(CT_Skip[i], 0, 1);												
									}
									dlgSpacing(5);
									dlgStretch(1);
								}
							}	
							dlgCell(0, celly++) {
								dlgVBoxLayout {					
									dlgLabel(" Rate");
									for (i=0; i < TopCounter;i++) {	
										dlgSpinBox(CT_Rate[i], 0,20);												
									}
									dlgSpacing(5);
								    dlgStretch(1);
								}
									
							}	
							 dlgCell(0, celly++) {
								dlgVBoxLayout {
									dlgLabel(" ");
									dlgStretch(1);
								}	
																				
							 }
						}
						
					}
					dlgVBoxLayout {
						dlgStretch(1);
					}
					
					
				
				
				}				
			}					
		
			dlgTabPage("PCB Bottom") {
				if (run_version==0) {
					dlgVBoxLayout {
						int celly=0;
						dlgGridLayout {
							dlgCell(0,celly++) {
						//	dlgMessageBox("!Value of maxComboLen_Bottom="+Num2Str(maxComboLen_Bottom*8), "&OK");   				
							string pl="<table width='100%'>"+
							"<tr><td width='60'>Reel #</td>"+
							"<td width='"+Num2Str(maxComboLen_Top*9)+"'>Parts Label/Quantity/Value/Package</td>"+
							"<td width='55'>Head</td>"+
							"<td width='70'>Height</td>"+
							"<td width='55'>Skip</td>"+
							"<td width='20'>Rate</td>"+
							"</tr>"+
							"</table>";						
							dlgLabel(pl);
							dlgStretch(1);
							}
										
						}				
						
						dlgGridLayout {
							int j=0;	
														
							for (j=0;j<MAXREEL;j++) {		
								int k=0;
								dlgCell(j, k) {										
									dlgLabel("Reel #"+Num2Str(j));
									dlgSpacing(5);							
									k++;							
								}
										
								dlgCell(j, k) {		
									switch (j) {
										case 0:  	dlgComboBox(components_Bottom, comboSelected_Bottom[0]) {
														
														// comboSelected_Bottom[0]: from 0 to max number of elements in components_Top
														  if(comboSelected_Bottom[0]==0) {  // ="*****Not used*****" 
															g_Efeeder_Bottom[comboSelected_Bottom[0]]=99;         // assign 99
														} else { 
															// components_Bottom[comboSelected_Bottom[0]]     selected content in string
															// components_Top_ptr[n]   // keep track of component
															// components_Bottom[n]=g_Ename[j] + "  " +equant+"  "+ g_Evalue[j] + "  " + g_Epackagename[j] ;		
															g_Efeeder_Bottom[comboSelected_Bottom[0]]=0; //selected content assign to feeder # 0
			
														}
														ReelNo_Bottom[0]= comboSelected_Bottom[0];	// Reel 0 is assigned with selected line
														CB_ReelNo[comboSelected_Bottom[0]]=0; 
														
													}
													break;
										case 1:  	dlgComboBox(components_Bottom, comboSelected_Bottom[1]) {
														if(comboSelected_Bottom[1]==0) {
															g_Efeeder_Bottom[comboSelected_Bottom[1]]=99;
														} else { 		
															g_Efeeder_Bottom[comboSelected_Bottom[1]]=1;
															
														}
														ReelNo_Bottom[1]=comboSelected_Bottom[1];
														CB_ReelNo[comboSelected_Bottom[1]]=1; 
													}
													break;	
										case 2:  	dlgComboBox(components_Bottom, comboSelected_Bottom[2]) {
														if(comboSelected_Bottom[2]==0) {
															g_Efeeder_Bottom[comboSelected_Bottom[2]]=99;
														} else {
															g_Efeeder_Bottom[comboSelected_Bottom[2]]=2;
														}
														ReelNo_Bottom[2]=comboSelected_Bottom[2];	
														CB_ReelNo[comboSelected_Bottom[2]]=2; 
													}
													break;
										case 3:  	dlgComboBox(components_Bottom, comboSelected_Bottom[3]) {
														if(comboSelected_Bottom[3]==0) {
															g_Efeeder_Bottom[comboSelected_Bottom[3]]=99;
														} else {
															g_Efeeder_Bottom[comboSelected_Bottom[3]]=3; 	
														}
														ReelNo_Bottom[3]=comboSelected_Bottom[3];	
														CB_ReelNo[comboSelected_Bottom[3]]=3; 
													}
													break;
										case 4:  	dlgComboBox(components_Bottom, comboSelected_Bottom[4]) {
														if(comboSelected_Bottom[4]==0) {
															g_Efeeder_Bottom[comboSelected_Bottom[4]]=99;
														} else {
															g_Efeeder_Bottom[comboSelected_Bottom[4]]=4;
														}
														ReelNo_Bottom[4]=comboSelected_Bottom[4];
														CB_ReelNo[comboSelected_Bottom[4]]=4; 	
													}	
													break;	
										case 5:  	dlgComboBox(components_Bottom, comboSelected_Bottom[5]) {
														if(comboSelected_Bottom[5]==0) {
															g_Efeeder_Bottom[comboSelected_Bottom[5]]=99;
														} else {
															g_Efeeder_Bottom[comboSelected_Bottom[5]]=5;
														}
														ReelNo_Bottom[5]= comboSelected_Bottom[5];
														CB_ReelNo[comboSelected_Bottom[5]]=5; 
																
													}
													
													break;			
										case 6:  	dlgComboBox(components_Bottom, comboSelected_Bottom[6]) {
														if(comboSelected_Bottom[6]==0) {
															g_Efeeder_Bottom[comboSelected_Bottom[6]]=99;
														} else {
															g_Efeeder_Bottom[comboSelected_Bottom[6]]=6;	
														}
														ReelNo_Bottom[6]=comboSelected_Bottom[6];
														CB_ReelNo[comboSelected_Bottom[6]]=6; 													
													}
													break;
										case 7:  	dlgComboBox(components_Bottom, comboSelected_Bottom[7]) {
														if(comboSelected_Bottom[7]==0) {
															g_Efeeder_Bottom[comboSelected_Bottom[7]]=99;
														} else {
															g_Efeeder_Bottom[comboSelected_Bottom[7]]=7;
														}
														ReelNo_Bottom[7]=comboSelected_Bottom[7];
														CB_ReelNo[comboSelected_Bottom[5]]=5; 	
														
													}
													break;	
										case 8:  	dlgComboBox(components_Bottom, comboSelected_Bottom[8]) {
														if(comboSelected_Bottom[8]==0) {
															g_Efeeder_Bottom[comboSelected_Bottom[8]]=99;
														} else {
															g_Efeeder_Bottom[comboSelected_Bottom[8]]=8;	
														}
														ReelNo_Bottom[8]=comboSelected_Bottom[8];	
														CB_ReelNo[comboSelected_Bottom[8]]=8; 	
													}
													break;
										case 9:  	dlgComboBox(components_Bottom, comboSelected_Bottom[9]) {
														if(comboSelected_Bottom[9]==0) {
															g_Efeeder_Bottom[comboSelected_Bottom[9]]=99;
														} else {
															g_Efeeder_Bottom[comboSelected_Bottom[9]]=9;
														}
														ReelNo_Bottom[9]=comboSelected_Bottom[9];	
														CB_ReelNo[comboSelected_Bottom[9]]=9; 	
													}
													break;
										case 10:  	dlgComboBox(components_Bottom, comboSelected_Bottom[10]) {
														if(comboSelected_Bottom[10]==0) {
															g_Efeeder_Bottom[comboSelected_Bottom[10]]=99;
														} else {
															g_Efeeder_Bottom[comboSelected_Bottom[10]]=10;	
														}
														ReelNo_Bottom[10]=comboSelected_Bottom[10];
														CB_ReelNo[comboSelected_Bottom[10]]=10; 	
													}
													break;	
										case 11:  	dlgComboBox(components_Bottom, comboSelected_Bottom[11]) {
														if(comboSelected_Bottom[11]==0) {
															g_Efeeder_Bottom[comboSelected_Bottom[11]]=99;
														} else {
															g_Efeeder_Bottom[comboSelected_Bottom[11]]=11;
																	
														}
														ReelNo_Bottom[11]=comboSelected_Bottom[11];
														CB_ReelNo[comboSelected_Bottom[11]]=11; 	
													}
													break;
										case 12:  	dlgComboBox(components_Bottom, comboSelected_Bottom[12]) {
														if(comboSelected_Bottom[12]==0) {
															g_Efeeder_Bottom[comboSelected_Bottom[12]]=99;
														} else {
															g_Efeeder_Bottom[comboSelected_Bottom[12]]=12;
														}
														ReelNo_Bottom[12]=comboSelected_Bottom[12];
														CB_ReelNo[comboSelected_Bottom[12]]=12; 	
													}
													break;
										case 13:  	dlgComboBox(components_Bottom, comboSelected_Bottom[13]) {
														if(comboSelected_Bottom[13]==0) {
															g_Efeeder_Bottom[comboSelected_Bottom[13]]=99;
														} else {
															g_Efeeder_Bottom[comboSelected_Bottom[13]]=13;
														}
														ReelNo_Bottom[13]=comboSelected_Bottom[13];
														CB_ReelNo[comboSelected_Bottom[13]]=13; 	
													}
													break;
										case 14:  	dlgComboBox(components_Bottom, comboSelected_Bottom[14]) {
														if(comboSelected_Bottom[14]==0) {
															g_Efeeder_Bottom[comboSelected_Bottom[14]]=99;
														} else {
															g_Efeeder_Bottom[comboSelected_Bottom[14]]=14;	
														}
														ReelNo_Bottom[14]=comboSelected_Bottom[14];
														CB_ReelNo[comboSelected_Bottom[14]]=14; 													
													}
													break;	
										case 15:  	dlgComboBox(components_Bottom, comboSelected_Bottom[15]) {
														if(comboSelected_Bottom[15]==0) {
															g_Efeeder_Bottom[comboSelected_Bottom[15]]=99;
														} else {
															g_Efeeder_Bottom[comboSelected_Bottom[15]]=15; 	
														}
														ReelNo_Bottom[15]=comboSelected_Bottom[15];
														CB_ReelNo[comboSelected_Bottom[15]]=15; 	
																
													}
													
													break;												
									}				
									dlgSpacing(5);							
									k++;							
								}	
								dlgCell(j, k) {						  
									dlgSpinBox(g_Head_Bottom[j],0,2);
									dlgSpacing(5);							
									k++;	
									
								}
								dlgCell(j, k) {	
									dlgRealEdit(g_Eheight_Bottom[j], 0, 3);	    												
									k++;
									dlgSpacing(5);
														
								}
								 dlgCell(j, k) {	
									dlgSpinBox(g_TapeSkip_Bottom[j], 0,1 );
									k++;							
									dlgSpacing(5);
								}	
								 dlgCell(j, k) {	
									dlgSpinBox(g_Erate_Bottom[j],0,20 );
									k++;							
									dlgSpacing(5);
								}		
								
								dlgCell(j, k) {				
									dlgSpacing(5);
									dlgLabel(" ");
									dlgStretch(1);		
									k++;							
								}
							}
						}
					}
				
				
					dlgVBoxLayout {
						dlgStretch(1);
					}
				}
				if (run_version==1) {
					dlgVBoxLayout {
						dlgGridLayout {
							int celly=0;
							dlgCell(0, celly++) {
								dlgVBoxLayout {
									dlgLabel("Parts Label            ");
									dlgSpacing(5);
									for (i=0; i < BottomCounter;i++) {
										dlgLabel(components_Bottom[i]);
										dlgSpacing(6);
									}
									
									dlgStretch(1);
								}
							}
							dlgCell(0, celly++) {
								dlgVBoxLayout {
									dlgLabel("Quantity ");
									dlgSpacing(5);
									for (i=0; i < BottomCounter;i++) {
										dlgLabel(component_quantity_Bottom[i]);
										dlgSpacing(6);
									}
								
									dlgStretch(1);
								}
							}	

							dlgCell(0, celly++) {
								dlgVBoxLayout {
									dlgLabel("Value    ");
									dlgSpacing(5);
									for (i=0; i < BottomCounter;i++) {
										dlgLabel(component_value_Bottom[i]);
										dlgSpacing(6);
									}
									
									dlgStretch(1);
								}	
							}


							dlgCell(0, celly++) {
								dlgVBoxLayout {
									dlgLabel("Package");
									dlgSpacing(5);
									for (i=0; i < BottomCounter;i++) {
										dlgLabel(component_packagename_Bottom[i]);
										dlgSpacing(6);
									}
									
									dlgStretch(1);
								}	
							}

							dlgCell(0,celly++) {
								dlgVBoxLayout {
									dlgLabel("Reel Assignment");
									for (i=0; i < BottomCounter;i++) {	
										dlgComboBox(Reel, CB_ReelNo[i]) { 
											// dlgMessageBox("You have selected " + Reel[CB_ReelNo[i]]);											
										} 									
									}
									dlgSpacing(5);
									dlgStretch(1);
								}	 
							}
							dlgCell(0, celly++) {
								dlgVBoxLayout {
									dlgLabel("Head");
									for (i=0; i < BottomCounter;i++) {	
										dlgSpinBox(CB_Ehead[i], 1, 2);												
									}
									dlgSpacing(5);
									dlgStretch(1);
								}	
								
							}	
							dlgCell(0, celly++) {
								dlgVBoxLayout {
									dlgLabel("Height");
									for (i=0; i < BottomCounter;i++) {	
										dlgRealEdit(CB_Eheight[i], 0.00, 3.00);												
									}
									dlgSpacing(5);
									dlgStretch(1);
								}	
								
							}	

							dlgCell(0, celly++) {
								dlgVBoxLayout {							
									dlgLabel("Skip");
									for (i=0; i < BottomCounter;i++) {	
										dlgSpinBox(CB_Skip[i], 0, 1);												
									}
									dlgSpacing(5);
									dlgStretch(1);
								}
							}	
							dlgCell(0, celly++) {
								dlgVBoxLayout {					
									dlgLabel(" Rate");
									for (i=0; i < BottomCounter;i++) {	
										dlgSpinBox(CB_Rate[i], 0,20);												
									}
									dlgSpacing(5);	
									dlgStretch(1);	
								}
															
							}	
							dlgCell(0, celly++) {
								dlgVBoxLayout {
									dlgLabel(" ");
									dlgStretch(1);
								}	
										
							}
						}	
					}
					dlgVBoxLayout {
						dlgStretch(1);
					}

					
				
				}	
			}
			// 1. load default values if new
			// 2. Load save values if settings file exist
			//
			dlgTabPage("Reel Configuration") {
				dlgVBoxLayout {
					dlgGridLayout {
					  
						int celly=0;
						dlgCell(0, celly++) {
							dlgVBoxLayout {
								dlgLabel("Reel Assignments");
								dlgSpacing(5);
								for (i=1; i <= MAXREEL;i++) {
									dlgLabel("Reel # "+Num2Str(i-1));
									dlgSpacing(6);
								}
								dlgStretch(1);
							}
							
						}
						dlgCell(0, celly++) {
							dlgVBoxLayout {
								dlgLabel("Reel Name");
								dlgSpacing(5);
								// ReelAlias[1]="Reel # 0"
								// ReelAlias[16]="Reel # 15"
								for (i=1; i <= MAXREEL;i++) {
									dlgStringEdit(ReelAlias[i]);					
															
								}
								dlgStretch(1);
							}
							
						}
						dlgCell(0, celly++) {
							dlgVBoxLayout {
								dlgLabel("Height");
								dlgSpacing(5);
								for (i=1; i <= MAXREEL;i++) {
									dlgRealEdit(ReelHeight[i],0.00,3);
									
								}
								dlgStretch(1);
							}
							
						}
						dlgCell(0, celly++) {
							dlgVBoxLayout {
								dlgLabel("Rate");
								dlgSpacing(5);
								for (i=1; i <= MAXREEL;i++) {
									dlgSpinBox(ReelRate[i],0,20);
									
								}
								dlgStretch(1);
							}
							
						}
						dlgCell(0, celly++) {
							dlgVBoxLayout {
								dlgLabel("Rotation Correction");
								dlgSpacing(5);
								for (i=1; i <= MAXREEL;i++) {
									dlgComboBox(RotationOffset,RotationOffsetSelected[i]);
								
								}
								dlgStretch(1);
							}
							
						}
						dlgCell(0, celly++) {
							dlgVBoxLayout {
							dlgLabel("                                     ");
								dlgSpacing(5);
								dlgStretch(1);
							}									
						}
					}
					dlgGridLayout {
					    int celly=0;
						dlgCell(1, celly++) {
						    dlgLabel(" ");  
							dlgStretch(1);							 
						}
						dlgCell(1, celly++) {
						   
							 dlgPushButton("Load Dangerous Prototypes's Standard Stack") {	
							  Load_Stack();							   
							  dlgRedisplay();
							  DP_stack_Loaded=1;
							  dlgMessageBox("!Dangerous Prototypes's Standard Stack Load\n", "&OK");  	
							 }
							dlgStretch(1);							 
						}
						dlgCell(1, celly++) {
						    dlgLabel(" ");  
							dlgStretch(1);							 
						}
						
						dlgCell(1, celly++) {
							dlgStretch(1);	
							 dlgPushButton("+&Accept") {
								for(i=1;i<=MAXREEL;i++) {	
									// Reel[0]="--------";		
									Reel[i]=ReelAlias[i];									
									for (j=0;j < TopCounter;j++) {
									     if (CT_ReelNo[j]==i) { 
											CT_Eheight[j]  =ReelHeight[i];
											CT_Rate[j]  =ReelRate[i];
										  }
									}	
									for (j=0;j < BottomCounter;j++) {
									     if (CB_ReelNo[j]==i) {
											CB_Eheight[j]  =ReelHeight[i];
											CB_Rate[j]  =ReelRate[i];
										  }
									}	
								
									
									
								}
								if (DP_stack_Loaded==1) {
										DP_stack_Loaded=2;
								}		
								dlgMessageBox("!New Reel Configuration Accepted \n PCB top and PCB Bottom values are updated too ", "&OK");  						
								
							}	
							  dlgPushButton("Cancel") {    
								 dlgReset();
								 dlgMessageBox("!Changes Cancelled", "&OK");								
								 };
							dlgStretch(1);							 
						}
						
						dlgCell(1, celly++) {
							dlgVBoxLayout {
								dlgLabel("                                     ");
								dlgSpacing(5);
								
								
								dlgStretch(1);
																							
							}
						}			
					          
					}
					dlgGridLayout {
						
						dlgCell(2, 0) {
							dlgHBoxLayout {		
								dlgLabel(Help1);  
								//dlgStretch(1);
							}		
						}
						dlgCell(3, 0) {
							dlgHBoxLayout {		
								dlgLabel(Help2);  
								//dlgStretch(1);
							}		
						}
					}
				}	
				dlgVBoxLayout {
						dlgLabel("   ");
						dlgStretch(1);
				}
				
			}
		} 
	};
	
	
	if (Result==1){
		
			
		fileerror();
				
		string csvfilename;
	
		int csv;
		for(csv=0;csv < 2 ; csv++) {
		    if (csv==0) {
				csvfilename=csvnametop;
			} else {
				csvfilename=csvnamebottom;
			}
			
			output(csvfilename) {
				line=1;
				if (debug==1) {
					printf("Partlist values\n");
					printf("Part,Value,Package,Library,CenterPointX,CenterPointY,Rotation\n");

					for (i=0;i<counter; i++) {
						 printf("%s,%s,%s,%s,%s,%s,%s\n",Ename[i],Evalue[i],Epackagename[i],ElibrarySource[i],EpartsX[i],EpartsY[i],Eangle[i]);
					}
					printf("\n");
				}
		
				// Board Origin		
				printf("%%,Origin,Offset,X,Y,,\n");
				printf("65535,0,%.2f,%.2f,,\n",Xorigin,Yorigin);
				printf("\n");
				
				// REEL Assignment
				string offsetx,offsety,comment;
				int ReelNo_G;
				printf("%%,Stack,Offset,Stack,X,Y,\n");
								
				for (j=0;j<MAXREEL;j++) {
					if (run_version==0) {
						if (csv==0) {    // top				
						  ReelNo_G = ReelNo_Top[j];				 
						} else {
						  ReelNo_G= ReelNo_Bottom[j];
						}
								 
						offsetx="0.00";
						offsety="0.00";	
						comment="FREE";	
						if (ReelNo_G!=99 )  {          //  && (CT_Elayer[ReelNo_Top[j]]="Top"))
						int inc=0;
						int kk;
						int pos;
						while (1) {
							string xy[];
							if (debug==1) {
								printf("DP_packages  %s\n",DP_Packages[inc]);
							}
							int fields= strsplit(xy,DP_Packages[inc++],'|'); 
							
							if (xy[0]=="EOL") {
								break;  // break out of while
							}
							if (csv==0) { //top
								 pos=strstr(CT_Epackagename[ReelNo_Top[j]],xy[0]);
								if (debug==1){
								   printf("POS VALUE = %d CT_Epackagename=%s xy[0]= %s\n", pos,CT_Epackagename[ReelNo_Top[j]],xy[0]);
								}
							} else {
								 pos =strstr(CB_Epackagename[ReelNo_Bottom[j]],xy[0]);
							}
							if (pos >= 0) {
								 offsetx= xy[1];
								 offsety= xy[2];
								 comment= xy[3];
								 if  (debug==1) {
									 if (csv==0) { //top
										printf("x=%s,y=%s,%s\n",offsetx,offsety,CT_Epackagename[ReelNo_Top[j]]);
									 }
									 else {
										printf("%s,%s,%s\n",offsetx,offsety,CB_Epackagename[ReelNo_Bottom[j]]);
									 }
								 }
								 break;           //break out of while		
							} else {
								offsetx="0.00";
								offsety="0.00";
								if ( csv==0) {
									comment=CT_Epackagename[ReelNo_Top[j]];
								} else {
									comment=CB_Epackagename[ReelNo_Bottom[j]];
								}
							}
			
						}
						if (debug==1) {
							if (csv==0) {
								printf("65535,1,%d,%s,%s,%s\n",j,offsetx,offsety,CT_Epackagename[ReelNo_Top[j]] );	
							} else {
								printf("65535,1,%d,%s,%s,%s\n",j,offsetx,offsety,CB_Epackagename[ReelNo_Bottom[j]] );	
	 
							} 
						} else {					
							printf("65535,1,%d,%s,%s,%s,\n",j,offsetx,offsety,comment );	
							
						}		
					} else {
						printf("65535,1,%d,%s,%s,%s,\n",j,offsetx,offsety,comment );	
						}
					}
					
					if (run_version==1) {
						int inc=0;								 
						offsetx="0.00";
						offsety="0.00";	
						comment="FREE";	
						if (csv==0) {
							for (i=0;i<TopCounter;i++) {   // try to scan all package, find content of CT_Reelno[i], match with j, when cT_Reel[i]=0 = "-----"
							
								if (CT_ReelNo[i] ==j+1) {    // has the reel # selected, if value is 0, no reel selected: value is 0 to 16,
								
									int pos;
									while (1) {
										string xy[];
										if (debug==1) {
											printf("DP_packages  %s\n",DP_Packages[inc]);
										}
										int fields= strsplit(xy,DP_Packages[inc++],'|'); 
									
										if (xy[0]=="EOL") {
											i=999;  // break out for
											break;  // break out of while
										}
										pos=strstr(component_packagename_Top[i],xy[0]);
										if (debug==1){
										   printf("POS VALUE = %d CT_Epackagename=%s xy[0]= %s\n", pos,component_packagename_Top[i],xy[0]);
										}
										
										if (pos >= 0) {
											 offsetx= xy[1];
											 offsety= xy[2];
											 comment= xy[3];
											 if  (debug==1) {											 
													printf("x=%s,y=%s,%s\n",offsetx,offsety,component_packagename_Top[i]);											
											 }
											 i=999;
											 break;           //break out of while		
										} else {
											offsetx="0.00";
											offsety="0.00";
											comment=component_packagename_Top[i];										
										}
					
									}
								
								} else {
									offsetx="0.00";
									offsety="0.00";	
									comment="FREE";	
								}
							
							}			
						} else {
							for (i=0;i<BottomCounter;i++) {   // try to scan all package, find content of CT_Reelno[i], match with j, when cT_Reel[i]=0 = "-----"
							
								if (CB_ReelNo[i] ==j+1) {    // has the reel # selected, if value is 0, no reel selected: value is 0 to 16,
								
									int pos;
									while (1) {
										string xy[];
										if (debug==1) {
											printf("DP_packages  %s\n",DP_Packages[inc]);
										}
										int fields= strsplit(xy,DP_Packages[inc++],'|'); 
									
										if (xy[0]=="EOL") {
											i=999;  // break out for
											break;  // break out of while
										}
											pos=strstr(component_packagename_Bottom[i],xy[0]);
										if (debug==1){
										   printf("POS VALUE = %d CT_Epackagename=%s xy[0]= %s\n", pos,component_packagename_Bottom[i],xy[0]);
										}
									
										if (pos >= 0) {
											 offsetx= xy[1];
											 offsety= xy[2];
											 comment= xy[3];
												 if  (debug==1) {											 
														printf("x=%s,y=%s,%s\n",offsetx,offsety,component_packagename_Bottom[i]);											
												 }
												 i=999;
												 break;           //break out of while		
										} else {
											offsetx="0.00";
											offsety="0.00";
											comment=component_packagename_Bottom[i];										
										}
					
									}
								
								} else {
									offsetx="0.00";
									offsety="0.00";	
									comment="FREE";	
								}
							
							}
					
					
						}
						printf("65535,1,%d,%s,%s,%s,\n",j,offsetx,offsety,comment );	
					}
				
				}
				printf("\n");
			
			
			int gx_rate=0;
			printf("%%,Feeding,Set,Stack,Feed Rate,\n");
			for (j=0;j<MAXREEL;j++) {
				if (run_version==0) {
					if (csv==0) { 				  
					  if (ReelNo_Top[j] !=99) {   // && (CT_Elayer[ReelNo_Top[j]]="Top"))
						gx_rate=g_Erate_Top[j];
					  }
					} else {
						if (ReelNo_Bottom[j] !=99) {   // && (CT_Elayer[ReelNo_Top[j]]="Top"))
						gx_rate=g_Erate_Bottom[j];
					  }
					}
				}
				if (run_version==1) {
				   
					if (csv==0) {
						for (i=0;i<TopCounter;i++) {  // scan to find feedrate
							if (CT_ReelNo[i] ==j+1) { 
							
							  gx_rate= CT_Rate[i];	
								break;
							}		
							
						}
					}else {
						for (i=0;i<BottomCounter;i++) {  // scan to find feedrate
							if (CB_ReelNo[i] ==j+1) { 
							   gx_rate= CB_Rate[i];	
								break;
							}		
							
						}
					
					}
				
					
				}
				printf("65535,2,%d,%d,\n",j, gx_rate);
				gx_rate=0;
			}
			
			
			printf("\n");
			//%,JointedBoardCommand,X,Y
            // 65535,3,1,0,0,0,0,0,
			printf("%%,Jointed,Board,X,Y\n");			
			printf("%%65535,3,0,0,0,0,0,0,\n\n");
			
			if ((nBoardsinX != 0) || (nBoardsinY != 0)) {
			// todo: Multiple boards 
			
			}
					
			// Part placement setup
			// Part placement
			// Part		Pickup 	Stack	X		Y		Rotation	Height	Skip	Reference	Comment
			// number 	head
			// 1		1		1	    4.00	22.00	-45			1		0		LED7	LED-805
			// 2		1		1		4.00	19.00	-45			1		0		LED8	LED-805
			// 3		1		1		4.00	16.00	-45			1		0		LED9	LED-805

			
			printf("%%,Head,Stack,X,Y,R,H,skip,Ref,Comment,\n");
			
					
			B.elements(E) {
				
				
			
				int wasSmd,				
				xmax =-2147483648,
				xmin = 2147483647,
				ymax = xmax,
				ymin = xmin;
				string smdlayer="";
				real angle = 0;

				wasSmd = 0;

				E.package.contacts(C) {
					if (C.smd && C.smd.layer == 1) {
					    smdlayer="Top";
						wasSmd = 1;
                    } else {
						smdlayer="Bottom";
						wasSmd = 1;
					
					}  
						if (C.x > xmax) xmax = C.x;
						if (C.y > ymax) ymax = C.y;
						if (C.x < xmin) xmin = C.x;
						if (C.y < ymin) ymin = C.y;
					
				}



				if (wasSmd){
					//angle of rotation starts from left side of origin
					// see 
					
				
					
					// Remove comment below if angle of rotation starts from right side of origin
					// 0 start at right side
					// if(E.angle >= 0 && E.angle < 270) {
						// angle =  90-E.angle;       // will output 90 to -179	
					// } else {
						// if(E.angle >= 270 && E.angle <=360 ) {    
							// angle = 450-E.angle	;	   //will output from 90 to 180
						// }
					// }		
					
				
					// find a match in the original:  
					//  numeric string g_Ename[],g_Evalue[],g_Epackagename[],g_ElibrarySource[],g_EpartsX[],g_EpartsY[],g_Elayer[],g_Efeeder[];
					//	int g_Equantity[],g_Erate[],g_Eangle[],g_TapeSkip[];
					//	real g_Eheight[];
					//grouping
					
					real partsheight;
					int skip,head;
					int stack;
					found=0;
					int i_got_it=0;
					int E_ptr;
					int Counterx;
					stack=99;
					if (csv==0) { 
						Counterx=TopCounter;
					} else {
						Counterx=BottomCounter;
					}
					if (debug==1) {
						for (j=0;j<Counterx;j++) { 
						   printf("Value of CT_ReelNo[%d]=%d Selected: %s\n",j,CT_ReelNo[j],Reel[CT_ReelNo[j]]);
						}
					}	
					for (j=0;j<Counterx;j++) { 
						if (run_version==0) {
						// locate where it belongs
						// find  E.name in CT_backptr[ReelNo_Top[k]]
						
							int i_got_it=0;
							for (k=0;k<MAXREEL;k++) {
								string a[];
								if (csv==0) { 
									n = strsplit(a, CT_backptr[ReelNo_Top[k]], '|'); 
								} else {
									n = strsplit(a, CB_backptr[ReelNo_Bottom[k]], '|'); 
								}
								for(l=0;l < n;l++) {
									E_ptr =strtol(alltrim(a[l])); 
									if(E.name==Ename[E_ptr]) {
										  // found e_ename
										i_got_it=1;
										stack=k;
										if (csv==0) { 
											partsheight=g_Eheight_Top[k];
											skip=g_TapeSkip_Top[k];
											head=g_Head_Top[k];						
										} else {
											partsheight=g_Eheight_Bottom[k];
											skip=g_TapeSkip_Bottom[k];
											head=g_Head_Bottom[k];
										}								
										break;  
									} else {
									   stack=99;
									   i_got_it=0;
									}
													
								}		
								if(i_got_it==1) {
									break;
								}
								
							}
							if(i_got_it==1) {
									break;
							}		
						}
						if (run_version==1) {
							string a[];
							int i_got_it=0;
							if(csv==0) {
								n = strsplit(a, components_Top[j], ','); 
							} else {
								n = strsplit(a, components_Bottom[j], ','); 
							}
							for(l=0;l < n;l++) {
								if (alltrim(E.name)==alltrim(a[l])) {
									i_got_it=1;
									break;
								} else {
									i_got_it=0;
								
								}
								
							
							
							}
							
							if (debug==1) {
									printf("Looking for %s seen component_Top[%d]= %s\n",E.name,j,components_Top[j]);
									
							}
						
						    if (i_got_it==1) {
								
								if (csv==0) {
										if (debug==2) {
											printf("Found component_Top[%d]= %s\n",j,components_Top[j]);
										}
								
										if (CT_ReelNo[j] !=0) {
											stack= CT_ReelNo[j]-1;   // contains reel#
										} else {
											stack=99;
										}
										
										partsheight=CT_Eheight[j];
										skip=CT_Skip[j];
										head=CT_Ehead[j];
										
								} else {
									if (debug==2) {
											printf("Found component_Bottom[%d]= %s\n",j,components_Bottom[j]);
										}
									 if (CB_ReelNo[j] !=0) {
										stack= CB_ReelNo[j]-1;   // contains reel#
									} else {
										stack=99;
									}
									partsheight=CB_Eheight[j];
									skip=CB_Skip[j];
									head=CB_Ehead[j];
								
								}
								if (debug==2) {
									   printf("Got it: stack= %d, height= %.2f, skip= %d, head = %d\n",stack,partsheight,skip,head);
									
								}
									i_got_it=0;
									break;
								}
							}
						
						}
						real PartsRotation=E.angle+(RotationOffsetSelected[stack+1]*90);
					    if (PartsRotation> 360) {
						   PartsRotation=PartsRotation-360;						
						}
						if(PartsRotation >= 0 && PartsRotation < 91)
							angle = -180 + (90-PartsRotation);		
		
						else if(PartsRotation > 90 && PartsRotation < 181)
							angle = 90 + (180-PartsRotation);

						else if(PartsRotation > 180 && PartsRotation < 271)
							angle = 0 + (270-PartsRotation);

						else if(PartsRotation > 270 && PartsRotation < 361)
							angle = -90 + (360-PartsRotation);
						if (debug==2) {
							if (RotationOffsetSelected[stack+1]!=0) {
						   printf("E.angle= %.2f, Offsetangle=%.2f, TM angle=%.2f  \n",E.angle,RotationOffsetSelected[stack+1]*90.0,angle);
						   }
						}
					     
						 
						if (stack != 99) {	
						
                      	
							printf("%d,%d,%d,%.2f,%.2f,%.0f,%.2f,%d,%s,%s-%s\n",line++,head,stack,u2mm((xmin + xmax)/2), u2mm((ymin + ymax)/2),angle,partsheight,skip, E.name,E.value,E.package.name);
						} else { 
							// no assigned stack
							if (debug==1) {
								printf("%d,%d,,%.2f,%.2f,%.0f,%.2f,%d,%s,%s-%s\n",line++,head,u2mm((xmin + xmax)/2), u2mm((ymin + ymax)/2),angle,partsheight,skip, E.name,E.value,E.package.name);
							}
						}
					
					
					} 
				
				
						
				}
			
		
			}
		}
		
		output(StackFname) {		       
		    if (run_version==0) {
				for(j=0; j < MAXREEL;j++) {
				   printf("[TOP]|%d|%d|%.2f|%d|%d\n",comboSelected_Top[j],g_Head_Top[j],g_Eheight_Top[j],g_TapeSkip_Top[j],g_Erate_Top[j]);
				}
				
				for(j=0; j < MAXREEL;j++) {
				   printf("[BOTTOM]|%d|%d|%.2f|%d|%d\n",comboSelected_Bottom[j],g_Head_Bottom[j],g_Eheight_Bottom[j],g_TapeSkip_Bottom[j],g_Erate_Bottom[j]);
				}
			}
			if (run_version==1) {
				for(j=0; j < TopCounter;j++) {
					  printf("[TOP]|%s|%d|%d|%.2f|%d|%d\n",components_Top[j],CT_ReelNo[j],CT_Ehead[j],CT_Eheight[j],CT_Skip[j],CT_Rate[j]);
				}
				for(j=0; j < BottomCounter;j++) {
				  printf("[BOTTOM]|%s|%d|%d|%.2f|%d|%d\n",components_Bottom[j],CB_ReelNo[j],CB_Ehead[j],CB_Eheight[j],CB_Skip[j],CB_Rate[j]);
				
				}
				for(j=0;j < MAXREEL;j++){
									  printf("[REEL]|%d|%s|%.2f|%d|%d\n",j,ReelAlias[j+1],ReelHeight[j+1],ReelRate[j+1],RotationOffsetSelected[j+1]);
	
				}
				
			
			}
		}
		// csv exported
		if (fileerror()) {
			dlgMessageBox(";Files are Open. CSV export Failed. \n", "&OK"); 
		   exit(1);
		} else {   
				dlgMessageBox(";CSV and PnP file export Success: \n "+csvnametop+"\n"+csvnamebottom+"\n"+StackFname+"\n", "&OK");  
		}	
       	
	}
} else {
	int ok= dlgMessageBox("!Board  must be open", "&OK");    
	
}   //  (project.board) project.board(B)
//dlgMessageBox("Value of Result"+ Num2Str(Result), "&OK"); 
exit(0);
